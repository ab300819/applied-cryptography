-/ This specification makes one slight deviation from standard ASN.1 syntax
   to overcome an annoyance in ASN.1 which requires a separate -- at the
   start of each and every line of comment.  Instead, this specification uses
   -//- comment delimiters (which work like C's /**/) in place of standard
   ASN.1 delimiters /-

cryptlib DEFINITIONS ::=
BEGIN

------------------------------------------------------------------------------
--																			--
--									Data Format								--
--																			--
------------------------------------------------------------------------------

-/ There are several variants of the PKCS #7/S/MIME/CMS format which gradually
   get more flexible (but not necessarily better) over time.  The initial
   format was PKCS #7 1.5 and earlier, 1.6 was a quick update which changed a
   number of SETs to SEQUENCEs (which don't require sorting of the encoded
   components), this doesn't appear to have been used by anything.  S/MIME 3/
   CMS was an extended form of S/MIME 2 which fiddled with some of the inner
   fields but was mostly the same as PKCS #7 1.5.  1.5 is a significant
   improvement on most of it's successors /-

ContentInfo ::= SEQUENCE {
	contentType		OBJECT IDENTIFIER,
	content		[0]	EXPLICIT ANY DEFINED BY contentType OPTIONAL
	}

-/ Raw data /-

Data ::= OCTET STRING						-- PKCS #7 1

-/ Authenticated data: Digested, signed, MAC'd data /-

DigestedData ::= SEQUENCE {					-- PKCS #7 5
	version				INTEGER (0),		-- PKCS #7 v1.5
	digestAlgorithm		AlgorithmIdentifier,-- v=2 for non id-Data
	encapContentInfo	SEQUENCE {
		contentType		OBJECT IDENTIFIER id-Data/Sig/Encr/Env,
		content   [ 0 ]	EXPLICIT OCTET STRING
		},
	digest				OCTET STRING
	}

SignedData ::= SEQUENCE {					-- PKCS #7 2
	version				INTEGER (1),		-- PKCS #7 v1.5
	digestAlgorithms	SET OF AlgorithmIdentifier,
	encapContentInfo	SEQUENCE {
		contentType		OBJECT IDENTIFIER id-Data/Sig/Encr/Env,
		content   [ 0 ]	EXPLICIT OCTET STRING
		}
	certificates  [ 0 ]	IMPLICIT SET OF Certificate,
	signerInfos			SET OF SignerInfo
	}

AuthenticatedData ::= SEQUENCE {			-- PKCS #9 16 1 2
	version				INTEGER (0),		-- S/MIME v3
	recipientInfos		SET OF RecipientInfo,
	macAlgorithm		AlgorithmIdentifier,
	encapContentInfo	SEQUENCE {
		contentType		OBJECT IDENTIFIER id-Data/Sig/Encr/Env,
		content   [ 0 ]	EXPLICIT OCTET STRING
		}
	mac					OCTET STRING
	}

-/ Encrypted data: Raw encrypted, enveloped /-

EncryptedData ::= SEQUENCE {				-- PKCS #7 6
	version				INTEGER (0),		-- PKCS #7 v1.5
	encrContentInfo		SEQUENCE {
		contentType		OBJECT IDENTIFIER id-Data/Sig/Encr/Env,
		contentEncrAlgo	AlgorithmIdentifier,
		content	  [ 0 ]	IMPLICIT OCTET STRING
		}
	}

EnvelopedData ::= SEQUENCE {				-- PKCS #7 3
	version				INTEGER (0),		-- PKCS #7 v1.5, v=2 for origInfo
	originatorInfo[ 0 ]	IMPLICIT SEQUENCE { [0] IMPLICIT SET OF Certificate } OPTIONAL,
	recipientInfos		SET OF RecipientInfo,
	encrContentInfo		SEQUENCE {
		contentType		OBJECT IDENTIFIER id-Data/Sig/Encr/Env,
		contentEncrAlgo	AlgorithmIdentifier,
		content	  [ 0 ]	IMPLICIT OCTET STRING
		}
	}

------------------------------------------------------------------------------
--																			--
--								Key Management								--
--																			--
------------------------------------------------------------------------------

-/ The parameters used to derive the conventional encryption key from the
   user key.  Usually we use the key directly, but sometimes it may have
   been derived from a longer user key, which is encoded in this record /-

PBKDF2 ::= SEQUENCE {						-- PKCS #5v2 key setup parameters
	algorithm		AlgorithmIdentifier (pkcs-5 12),
	params			SEQUENCE {
		salt		OCTET STRING,			-- Key setup salt
		iterationCount						-- Key setup iterations
					INTEGER (1..MAX),
		}
	}

-/ CMS key transport information /-

KeyTransRecipientInfo ::= SEQUENCE {		-- CMS - S/MIME
	version			INTEGER (0),			-- CMS
	issuerAndSerial	IssuerAndSerialNumber,	-- Encrypting certificate
	algorithm		AlgorithmIdentifier,	-- Encryption algorithm
	encryptedKey	OCTET STRING			-- Encryped key
	}
KeyTransRecipientInfo ::= SEQUENCE {		-- CMS - cryptlib
	version			INTEGER (2),			-- CMS
	keyID	  [ 0 ]	SubjectKeyIdentifier,	-- Key ID of encrypting key
	algorithm		AlgorithmIdentifier,	-- Encryption algorithm
	encryptedKey	OCTET STRING			-- Encrypted key
	}

-/ cryptlib/CMS key agreement information, which is officially called
   KeyAgreeRecipientInfo but in order for it to make sense it really needs
   to be named FortezzaRecipientInfo /-

FortezzaRecipientInfo ::= SEQUENCE {		-- CMS - S/MIME
	version			INTEGER (3),			-- CMS
	originator[ 0 ]	EXPLICIT [ 0 ] SubjectKeyIdentifier,-- Originator pub.key
	ukm		  [ 1 ]	EXPLICIT OCTET STRING,	-- Nonce, Ra
	algorithm		AlgorithmIdentifier,	-- Fortezza key wrap OID
	recipientKeys	SEQUENCE OF SEQUENCE {
		rKeyId[ 0 ]	IMPLICIT SEQUENCE { SubjectKeyIdentifier }, -- Recip.pubk
		encryptedKey OCTET STRING			-- Encr.key info, TEK( MEK )
		}
	}

-/ CMS conventional key transport information.  This structure is somewhat
   misnamed since it's really just a kludge to work with pre-distributed
   shared RC2 or 3DES keys for S/MIME-based mailing lists and not a general-
   purpose KEK object /-

KEKRecipientInfo ::= SEQUENCE {
	version			INTEGER (4),			-- CMS
	kekid			SEQUENCE {
		keyIdent	OCTET STRING			-- Magic ID for KEK
		},
	keyEncAlgo		AlgorithmIdentifier,	-- Key wrap algorithm
	encryptedKey	OCTET STRING			-- Encrypted key
	}

-/ CMS password-based key transport information.  This is also misnamed since
   it's actually general-purpose and does what KEKRecipientInfo should do /-

PasswordRecipientInfo ::= SEQUENCE {
	version			INTEGER (0),			-- CMS
	derivationAlgorithm						-- KEK derivation algorithm,
			  [ 0 ]	AlgorithmIdentifier OPTIONAL,	-- PBKDF2 if present
	algorithm		AlgorithmIdentifier,	-- KEK algorithm
	encryptedKey	OCTET STRING
	}

-/ CMS key management /-

RecipientInfo ::= CHOICE {
	ktri			KeyTransRecipientInfo,	-- Public-key encrypted key
	kari	  [ 1 ] FortezzaRecipientInfo,	-- Fortezza key-agreement info
	kekri	  [ 2 ] KEKRecipientInfo,		-- Conventionally encrypted key
	pwri	  [ 3 ]	PasswordRecipientInfo	-- Password-encrypted key
	}

------------------------------------------------------------------------------
--																			--
--									Signatures								--
--																			--
------------------------------------------------------------------------------

-/ CMS signature information /-

SignerInfo ::= SEQUENCE {					-- CMS - S/MIME
	version			INTEGER (1),			-- CMS
	issuerAndSerial	IssuerAndSerialNumber,	-- Signing certificate
	hashAlgorithm	AlgorithmIdentifier,	-- Hash algorithm type
	signedAttributes						-- Authenticated attributes
			  [ 0 ]	IMPLICIT SET OF Attribute OPTIONAL,
	signatureAlgorithm						-- Signature algorithm type
					AlgorithmIdentifier,
	signature		OCTET STRING			-- The signature itself
	}
SignerInfo ::= SEQUENCE {					-- CMS - cryptlib
	version			INTEGER (3),			-- CMS
	keyID	  [ 0 ]	SubjectKeyIdentifier,	-- Key ID of signing key
	hashAlgorithm	AlgorithmIdentifier,	-- Hash algorithm type
	signatureAlgorithm						-- Signature algorithm type
					AlgorithmIdentifier,
	signature		OCTET STRING			-- The signature itself
	}

------------------------------------------------------------------------------
--																			--
--								Public/Private Keys							--
--																			--
------------------------------------------------------------------------------

-/ PKCS #15 uses a very object-oriented design which follows PKCS #11 and
   uses a lot of the expressive power of ASN.1 in the specification of its
   PDU's.  The basic PKCS #15 object is defined as follows:

	PKCS15Object( ClassAttributes, SubclassAttributes, TypeAttributes ) ->
		SEQUENCE {
			commonAttr		CommonObjectAttributes,
			classAttr		ClassAttributes,
			subclassAttr[0]	SubclassAttributes OPTIONAL,
			typeAttr	[1]	TypeAttributes
			}

   with the attributes being filled in on a per-object basis.  Every object
   contains common object attributes, and every key or certificate object
   contains common key or cert class attributes.  In addition the public and
   private key subclasses contain subclass-specific atyributes, but they 
   don't contain anything which isn't present elsewhere so they're omitted:

	SEQUENCE {
		SEQUENCE {
			label		UTF8String OPTIONAL,
			...
			},
		SEQUENCE {		-- Key				SEQUENCE {		-- Cert
			iD			OCTET STRING,			iD			OCTET STRING,
			usage		BIT STRING,				authority	BOOLEAN DEF FALSE,
			native		BOOLEAN FALSE,			trusted	[1] SEQUENCE { usage BIT STR },
			accessFlags	BIT STRING OPTIONAL,	keyID	[2] SEQUENCE OF KeyID,
			...									impTrust[3]	BOOLEAN DEFAULT FALSE,
			},									...
												},
		[0] EXPLICIT SEQUENCE {} OPTIONAL,
		[1] EXPLICIT SEQUENCE {
			<data>
			}
		} /-

PKCS15CommonObjectAttributes ::= SEQUENCE {
	label			UTF8String OPTIONAL,	-- Object label
	...
	}

-/ Class attributes /-

PKCS15CommonKeyAttributes ::= SEQUENCE {
	iD				OCTET STRING,			-- Cross-reference to cert
	usage			BIT STRING,				-- PKCS #11 usage flags
	native			BOOLEAN FALSE,			-- Not a hardware crypto key
	accessFlags		BIT STRING b'01101' OPT,-- PKCS #11 access flags
	...
	}

PKCS15CommonCertificateAttributes ::= SEQUENCE {
	iD				OCTET STRING,			-- Cross-reference to key
	authority		BOOLEAN DEFAULT FALSE,	-- CA flag
	dummy			SEQUENCE {} OPTIONAL,	-- Not used
	dummy	  [ 0 ]	SEQUENCE {} OPTIONAL,	-- Not used
	trusted	  [ 1 ]	SEQUENCE {
		keyUsage	BIT STRING,				-- Key usage cert is trusted for
		...
		} OPTIONAL,
	keyID	  [ 2 ]	SEQUENCE OF KeyID OPTIONAL,
	impTrust  [ 3 ]	BOOLEAN OPTIONAL,
	...
	}

PKCS15CommonDataObjectAttributes ::= SEQUENCE {
	applicationName	UTF8String OPTIONAL,	-- One or both must be present
	applicationOID	OBJECT IDENTIFIER OPTIONAL,
	...
	}

-/ Key identifiers /-

PKCS15KeyIdentifier ::= TYPED CHOICE {
	iAndS			SEQUENCE {				-- Converted to iAndSHash on read
		id			INTEGER (1),
		value		IssuerAndSerialNumber
		},
	subjectKeyID	SEQUENCE {				-- Only used it different from iD
		id			INTEGER (2),
		value		OCTET STRING
		},
	iAndSHash		SEQUENCE {				-- Written and read
		id			INTEGER (3),
		value		OCTET STRING SIZE(20)
		},
	iHash			SEQUENCE {				-- Written and read
		id			INTEGER (6),
		value		OCTET STRING SIZE(20
		},
	sHash			SEQUENCE {				-- Written and read
		id			INTEGER (7),
		value		OCTET STRING SIZE(20
		},
	...
	}

-/ Private key information (DLP = DSA/DH/KEA/etc) /-

PKCS15PrivateRSAKeyAttributes ::= SEQUENCE {
	value		  [ 0 ]	IMPLICIT SEQUENCE {	-- Or [2] IMPLICIT EnvelopedData
		modulus	  [ 0 ]	INTEGER OPTIONAL,	-- n
		publicExp [ 1 ]	INTEGER OPTIONAL,	-- e
		privateEx [ 2 ]	INTEGER OPTIONAL,	-- d
		prime1	  [ 3 ]	INTEGER OPTIONAL,	-- p
		prime2	  [ 4 ]	INTEGER OPTIONAL,	-- q
		exponent1 [ 5 ]	INTEGER OPTIONAL,	-- d mod p-1
		exponent2 [ 6 ]	INTEGER OPTIONAL,	-- d mod q-1
		coefficie [ 7 ]	INTEGER OPTIONAL	-- q^-1 mod p
		},
	modulusLength		INTEGER,
	...
	}

PKCS15PrivateDLPKeyAttributes ::= SEQUENCE {-- Or [2] IMPLICIT EnvelopedData
	value		  [ 0 ]	IMPLICIT
						INTEGER,			-- DSA x value
	...
	}

PKCS15PrivateKey ::= CHOICE {
	privateRSAKey		PKCS15Object{ PKCS15CommonKeyAttributes,
									  PKCS15CommonPrivateKeyAttributes,
									  PKCS15PrivateRSAKeyAttributes },
	privateDSAKey [ 2 ]	PKCS15Object{ PKCS15CommonKeyAttributes,
									  PKCS15CommonPrivateKeyAttributes,
									  PKCS15PrivateDSAKeyAttributes }
	}

-/ Public key information (DLP = DSA/DH/KEA/etc) /-

PKCS15PublicRSAKeyAttributes ::= SEQUENCE {
	value		  [ 0 ]	EXPLICIT
				  [ 1 ]	IMPLICIT SubjectPublicKeyInfo,
	modulusLength		INTEGER,
	...
	}

PKCS15PublicDLPKeyAttributes ::= SEQUENCE {
	value		  [ 0 ]	EXPLICIT SubjectPublicKeyInfo,
	...
	}

PKCS15PublicKey ::= CHOICE {
	publicRSAKey		PKCS15Object{ PKCS15CommonKeyAttributes,
									  PKCS15CommonPublicKeyAttributes,
									  PKCS15PublicRSAKeyAttributes },
	publicDSAKey  [ 2 ]	PKCS15Object{ PKCS15CommonKeyAttributes,
									  PKCS15CommonPublicKeyAttributes,
									  PKCS15PublicDSAKeyAttributes }
	}

-/ Certificate information /-

PKCS15X509CertificateAttributes ::= SEQUENCE {
	value		  [ 0 ]	IMPLICIT Certificate,
	...
	}

PKCS15Certificate ::= CHOICE {
	x509Certificate		PKCS15Object{ PKCS15CommonCertificateAttributes,
									  NULL,
									  PKCS15X509CertificateAttributes }
	}

-/ Data information /-

ConfigOption ::= SEQUENCE {
	type				INTEGER,			-- CRYPT_PROPERTY_xxx
	value				ANY DEFINED BY type	-- BOOLEAN, INTEGER, UTF8String
	}

PKCS15Opaque ::= [ 0 ] IMPLICIT SEQUENCE OF ConfigOption

PKCS15Data ::= [0] PKCS15Object { PKCS15CommonDataObjectAttributes,
								  NULL,
								  PKCS15Opaque }

-/ Overall object wrappers. The tagging is [n] PKCS15Objects.foo
   [0] PKCS15ObjectValue.objects /-

PrivateKeys ::= [0] EXPLICIT SEQUENCE {
					[0] EXPLICIT SEQUENCE OF PKCS15PrivateKey }
PublicKeys ::= [1] EXPLICIT SEQUENCE {
					[0] EXPLICIT SEQUENCE OF PKCS15PublicKey }
Certificates ::= [4] EXPLICIT SEQUENCE {
					[0] EXPLICIT SEQUENCE OF PKCS15Certificate }
DataObjects ::= [7] EXPLICIT SEQUENCE {
					[0] EXPLICIT SEQUENCE OF PKCS15Data }

------------------------------------------------------------------------------
--																			--
--						Certificate Mismanagement Protocol					--
--																			--
------------------------------------------------------------------------------

-/ "If an undergraduate student handed this in as an assignment I'd fail them
	on the grounds that it shows a complete lack of understanding of the
	principles of workable protocol design" /-

InitRequest ::= SEQUENCE {					-- p.11, profile = p.34
	header				SEQUENCE {			-- p.12
		version			INTEGER (2),
		sender			SEQUENCE {},
		recipient	[4]	EXPLICIT DirectoryName,	-- DN of CA
		protAlgo	[1]	EXPLICIT AlgorithmIdentifier (PBMac),-- p.14
		macKeyID	[2] EXPLICIT OCTET STRING,
		transID		[4] EXPLICIT OCTET STRING SIZE (16),	-- Random
		nonce		[5] EXPLICIT OCTET STRING SIZE (16),	-- Random
		}
	body			[0]	EXPLICIT SEQUENCE {
						SEQUENCE {
		certReqMsg		SEQUENCE {			-- p.1
						SEQUENCE {			-- p.4
			cReqID		INTEGER (0),
			cTemplate	SEQUENCE {
				subject	[5] EXPLICIT Name,
				pubKey	[6] SubjectPublicKeyInfo,
				exts	[9] Extensions OPTIONAL
						}
					}
		pop			[1] Signature			-- From X.509
				}
			}
		}
	protection		[0]	EXPLICIT BIT STRING	-- Contains 20-byte MAC
	}

InitResponse ::= SEQUENCE {					-- p.11, profile = p.35
	header				SEQUENCE {			-- p.12
		version			INTEGER (2),
		sender			SEQUENCE {...},		-- Ignored
		recipient		SEQUENCE {...},		-- Ignored
		messageTime	[0]	EXPLICIT GeneralisedTime,	-- Ignored
		protAlgo	[1]	EXPLICIT AlgorithmIdentifier (PBMac),	-- p.14
		macKeyID	[2]	EXPLICIT OCTET STRING,			-- Must match previous
		transID		[4] EXPLICIT OCTET STRING SIZE (16),-- Must match previous
		nonceX		[5] EXPLICIT OCTET STRING SIZE (16),-- Needed in CertConf
		...
		}
	body			[3] EXPLICIT SEQUENCE {			-- p.19
		dummy		[1] EXPLICIT SEQUENCE {...},	-- Ignored
		response		SEQUENCE {
			certReqID	INTEGER (0),
			status		SEQUENCE {			-- p.16
				status	INTEGER,
				...
				}
			certKeyPair	SEQUENCE {			-- If status == 0 or 1
				cert[0]	EXPLICIT Certificate,
				...
				}
			}
		}
	}

CertConf ::= SEQUENCE {						-- p.11, profile = p.35
	header				SEQUENCE {			-- p.12
		version			INTEGER (2),
		sender			SEQUENCE {...},		-- Ignored
		recipient		SEQUENCE {...},		-- Ignored
		messageTime	[0]	EXPLICIT GeneralisedTime,	-- Ignored
		protAlgo	[1]	EXPLICIT AlgorithmIdentifier (PBMac),	-- p.14
		macKeyID	[2]	EXPLICIT OCTET STRING,			-- Must match previous
		transID		[4] EXPLICIT OCTET STRING SIZE (16),-- Must match previous
		nonce		[5] EXPLICIT OCTET STRING SIZE (16),-- Random
		nonceX		[6] EXPLICIT OCTET STRING SIZE (16),-- Copied from InitResp
		...
		}
	body		   [24]	EXPLICIT SEQUENCE {			-- p.19
						SEQUENCE {
		certHash		OCTET STRING
			}
		}
	}

Conf ::= SEQUENCE {						-- p.11, profile = p.35
	header				SEQUENCE {			-- p.12
		version			INTEGER (2),
		sender			SEQUENCE {...},		-- Ignored
		recipient		SEQUENCE {...},		-- Ignored
		messageTime	[0]	EXPLICIT GeneralisedTime,	-- Ignored
		protAlgo	[1]	EXPLICIT AlgorithmIdentifier (PBMac),	-- p.14
		macKeyID	[2]	EXPLICIT OCTET STRING,			-- Must match previous
		transID		[4] EXPLICIT OCTET STRING SIZE (16),-- Must match previous
		...
		}
	body		   [19]	EXPLICIT SEQUENCE {			-- p.19
						NULL
		}
	}

END
